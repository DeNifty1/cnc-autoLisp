(defun c:rem ()
        (setq osmo (getvar "osmode"))
        (setvar "osmode" 0)
        (setq p1 (getpoint "\nPick begining point of remnant: "))
        (setq y1 (getstring "\nEnter Y: "))
        (command "line" p1 (strcat "@0," y1 ) "")
        (setq a 0)
        (while (/= a nil)
                (setq x (getstring "\nEnter X: ")) 
                (if (= x "")
                        (setq a nil)
                        (command "line" "" (strcat "@" x ",0" ) "" )
                )
                (setq y2 (getstring "\nEnter Y: ")) 
                (if (= y2 "")
                        (setq a nil)
                        (command "line" "" (strcat "@0," y2 ) "" )
                )
        )
        (setvar "osmode" osmo)
        (setq p4 (entsel "\nFirst point of fillet (to make polyline): "))
        (setq p5 (entsel "\nSecond point of fillet (to make polyline): "))
        (command "fillet" p4 p5)
        (setq p2 (getpoint "\nPick first point of window (to make polyline): "))
        (setq p3 (getcorner p2 "\nPick second point of window (to make polyline): "))
        (command "pedit" p4 "y" "j" "w" p2 p3 "" "")
        (command "area" "E" (entlast))
)
