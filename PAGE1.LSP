(defun c:page1()
        (graphscr)
        (setvar "pickbox" 6)
        (command "zoom" "w" "29.37,26.93" "37.87,39.93")
        (setq true 1)
        (setq x 30.4)
        (setq y 36.44)
        (while (<= true 30)
                (setq p1 (list x y))
                (command "ddatte" p1)
                (setq y (- y 0.31))
                (setq next nil)
             ;;;Ask user if next block needs editing 
                (setq next (getstring "Enter command: or <enter> to continue editing\n"))
                (if (= next "")
                        (setq true (+ true 1))
                        (progn
                        (setq true 31)
                        (command next)
                        )
                )
        )
)
